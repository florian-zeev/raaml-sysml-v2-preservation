package Milestone2ResolvedCarriers {
    metadata def RaamlStereotype;

    occurrence def PlainLibraryClass;

    part def BlockLibraryClass;

    constraint def ConstraintBlockLibraryClass;

    enum def ValueTypeEnumeration {
        low;
        high;
    }
}
